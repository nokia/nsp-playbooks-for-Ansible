module iplink {
  namespace "urn:nokia.com:nsp:yang:im:iplink";

  prefix iplink;

  organization
    "NSP DevOps";
  contact
    "NSP DevOps";
  description
    "";

  revision "2026-02-18" {
    description
      "Initial revision.";
  }

  container iplink {

    description
        "Physical/logical interfaces (including IGP/MPLS) to connect two routers.";

    leaf description {
      description "Used to populate description fields for node-level configuration objects.";
      type string;
    }
    
    leaf admin-state {
      description "Used to administratively enable/disable interfaces and protocol bindings";
      type enumeration {
        enum enable;
        enum disable;
      }
      default "enable";
    }
    
    container endpoint-a {
      leaf ne-id {
        description "ne-id of the first router.";
        type string;
        mandatory true;
      }
      leaf port-id {
        description "physical port of the first router.";
        type string;
        mandatory true;
      }
    }
    container endpoint-b {      
      leaf ne-id {
        description "ne-id of the second router.";
        type string;
        mandatory true;
      }
      leaf port-id {
        description "physical port of the second router.";
        type string;
        mandatory true;
      }
    }
  }
  
  container iplink-state {
    config false;
    leaf oper-state {
      type string;
    }
    leaf subnet {
      type string;
    }
    leaf speed {
      type string;
    }
    container performance {
      leaf round-trip-delay {
        type uint32;
        units "microseconds";
      }
      leaf round-trip-jitter {
        type uint32;
        units "microseconds";
      }
      leaf frame-loss-ratio {
        type uint32;
        units "millipercent";
      }
      leaf utilization {
        type uint32 {
            range "0..10000";
        }
        units "centipercent";
      }
    }    
  }  
}
